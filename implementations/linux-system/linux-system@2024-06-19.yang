module linux-system {
    namespace "http://linux.org";
    prefix "lin";

    import ietf-inet-types {
	prefix inet;
    }

    import ietf-system {
	prefix sys;
    }

    import clixon-lib {
        prefix cl;
    }

    organization
	"MontaVista Software";

    contact
	"http://mvista.com
         Corey Minyard - cminyard@mvista.com";

    description
	"This module extends ietf-system for newer things in Linux.  New
         items are:
         * New password hash types.
         * NTP NTS-KE support, NTP over TLS
         * use-vc DNS option support
         * certificates for DNS
         * features for resolv.conf dns or dnsproxy

         Copyright (C) 2024 MontaVista Software, LLC <source@mvista.com>

         Licensed under the Apache License, Version 2.0 (the \"License\");
         you may not use this file except in compliance with the License.
         You may obtain a copy of the License at

            http://www.apache.org/licenses/LICENSE-2.0

         Unless required by applicable law or agreed to in writing, software
         distributed under the License is distributed on an \"AS IS\" BASIS,
         WITHOUT WARRANTIES OR CONDITIONS OF ANY KIND, either express or
         implied.
         See the License for the specific language governing permissions and
         limitations under the License.";

    revision 2024-06-19 {
	description
	    "Initial revision.";
    }

    feature old-dns {
	description
	    "Indicates that the device supports old-style, non-systemd
             dns configuration.";
    }

    feature dnsproxy {
	description
	    "Indicates that the device supports dnsproxy dns
             configuration.";
    }

    feature chrony-ntp {
	description
	    "Indicates that the device supports NTP via chrony.";
    }

    typedef crypt-hash-shadow {
	type string {
	    pattern
		'x'
	      + '|$0$.*'
	      + '|$1$[a-zA-Z0-9./]{1,8}$[a-zA-Z0-9./]{22}'
              + '|$5$(rounds=\d+$)?[a-zA-Z0-9./]{1,16}$[a-zA-Z0-9./]{43}'
              + '|$6$(rounds=\d+$)?[a-zA-Z0-9./]{1,16}$[a-zA-Z0-9./]{86}'
              + '|$y$[a-zA-Z0-9./]{1,8}$[a-zA-Z0-9./]{22}$[a-zA-Z0-9./]{43}'
              + '|$gy$[./A-Za-z0-9]+$[./A-Za-z0-9]{,86}$[./A-Za-z0-9]{43}'
              + '|$7$[./A-Za-z0-9]{11,97}$[./A-Za-z0-9]{43}'
              + '|$2[abxy]$[0-9]{2}$[./A-Za-z0-9]{53}'
              + '|$sha1$[1-9][0-9]+$[./0-9A-Za-z]{1,64}$[./0-9A-Za-z]{8,64}[./0-9A-Za-z]{32}'
              + '|$md5(,rounds=[1-9][0-9]+)?$[./0-9A-Za-z]{8}${1,2}[./0-9A-Za-z]{22}';
	}
	description
	    "An extension of iana-crypt-hash to add newer hashing types.  The
	    'x' value is returned as a dummy value to avoid returning actual
            password data.";
    }

    augment "/sys:system" {
	cl:system-only-config {
	    description
		"All of ietf-system/linux-system is system-only.";
	}
    }

    deviation /sys:system/sys:authentication/sys:user/sys:password {
	deviate replace {
	    type crypt-hash-shadow;
	}
	description
	    "This type is an extension of the IANA type that adds
             newer hashes that Linux uses.  It is backwards
             compatible with the old type";
    }

    //deviation /sys:system/sys:dns-resolver {
    //	deviate not-supported;
    //	description
    //	    "We don't support old DNS resolving, we use systemd's
    //             resolver.  So we don't want anyone touching this stuff.";
    //}

    augment "/sys:system/sys:dns-resolver/sys:options" {
	leaf use-vc {
	    type boolean;
	    default false;
	    description
		"Indicates whether to use UDP (false) or TCP (true).";
	}
    }

    augment "/sys:system/sys:dns-resolver" {
	leaf certificate {
	    type string;
	    description
		"The certificate file used to validate the servers.";
	}
    }

    augment "/sys:system/sys:ntp/sys:server/sys:transport" {
	case nts {
            container nts {
		description
		    "Contains TCP-specific configuration parameters
                     for NTP over TLS, with NTS-KE.";
		leaf address {
		    type inet:host;
		    mandatory true;
		    description
			"The address of the NTP server.";
		}
		leaf port {
		    if-feature sys:ntp-udp-port;
		    type inet:port-number;
		    default 123;
		    description
			"The port number of the NTP server.";
		}
		leaf ntsport {
		    type inet:port-number;
		    default 4460;
		    description
			"The port number of the NTP server.";
		}
		leaf certificate {
		    type string;
		    mandatory true;
		    description
			"The certificate used to validate the server.  If
			 not provided, defaults to the standard system
			 certificates.";
		}
            }
	}
    }
}
