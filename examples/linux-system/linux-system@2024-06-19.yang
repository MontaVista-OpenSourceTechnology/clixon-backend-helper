module linux-system {
    namespace "http://linux.org";
    prefix "lin";

    import ietf-system {
	prefix ietf;
    }

    organization
	"MontaVista Software";

    contact
	"http://mvista.com
         Corey Minyard - cminyard@mvista.com";

    description
	"This module extends ietf-system for newer things in Linux.  New
         items are:
         * New password hash types.
         * systemd DNS resolver.
         * NTP NTS-KE support, NTP over TLS.g";

    revision 2024-06-19 {
	description
	    "Initial revision.";
    }

    feature old-dns {
	description
	    "Indicates that the device supports old-style, non-systemd
             dns configuration.";
    }

    typedef crypt-hash-shadow {
	type string {
	    pattern
		'$0$.*'
	      + '|$1$[a-zA-Z0-9./]{1,8}$[a-zA-Z0-9./]{22}'
              + '|$5$(rounds=\d+$)?[a-zA-Z0-9./]{1,16}$[a-zA-Z0-9./]{43}'
              + '|$6$(rounds=\d+$)?[a-zA-Z0-9./]{1,16}$[a-zA-Z0-9./]{86}'
              + '|$y$[a-zA-Z0-9./]{1,8}$[a-zA-Z0-9./]{22}$[a-zA-Z0-9./]{43}'
              + '|$gy$[./A-Za-z0-9]+$[./A-Za-z0-9]{,86}$[./A-Za-z0-9]{43}'
              + '|$7$[./A-Za-z0-9]{11,97}$[./A-Za-z0-9]{43}'
              + '|$2[abxy]$[0-9]{2}$[./A-Za-z0-9]{53}'
              + '|$sha1$[1-9][0-9]+$[./0-9A-Za-z]{1,64}$[./0-9A-Za-z]{8,64}[./0-9A-Za-z]{32}'
              + '|$md5(,rounds=[1-9][0-9]+)?$[./0-9A-Za-z]{8}${1,2}[./0-9A-Za-z]{22}';
	}
	description
	    "An extension of iana-crypt-hash to add newer hashing types.";
    }

    deviation /ietf:system/ietf:authentication/ietf:user/ietf:password {
	deviate replace {
	    type crypt-hash-shadow;
	}
	description
	    "This type is an extension of the IANA type that adds
             newer hashes that Linux uses.  It is backwards
             compatible with the old type";
    }

    //deviation /ietf:system/ietf:dns-resolver {
    //	deviate not-supported;
    //	description
    //	    "We don't support old DNS resolving, we use systemd's
    //             resolver.  So we don't want anyone touching this stuff.";
    //}

    augment "/ietf:system/ietf:dns-resolver/ietf:options" {
	leaf use-vc {
	    type boolean;
	    default false;
	    description
		"Indicates whether to use UDP (false) or TCP (true).";
	}
    }

    augment "/ietf:system/ietf:dns-resolver/ietf:server" {
	leaf certificate {
	    type binary;
	    description
		"The certificate used to validate the server.";
	}
    }

    augment "/ietf:system/ietf:ntp/ietf:server/ietf:transport" {
	case tcp {
            container tcp {
		description
		    "Contains TCP-specific configuration parameters
                     for NTP over TLS, with NTS-KE.";
		leaf address {
		    type inet:host;
		    mandatory true;
		    description
			"The address of the NTP server.";
		}
		leaf port {
		    if-feature ntp-udp-port;
		    type inet:port-number;
		    default 4460;
		    description
			"The port number of the NTP server.";
		}
		leaf certificate {
		    type binary;
		    description
			"The certificate used to validate the server.  If
			 not provided, defaults to the standard system
			 certificates.";
		}
            }
	}
    }
}
