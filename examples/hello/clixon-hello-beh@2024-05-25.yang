module clixon-hello-beh {
    yang-version 1.1;
    namespace "http://clixon_beh/hello";
    prefix he;
    revision 2024-05-25 {
	description
	    "Clixon backend helper hello world example

             Copyright (C) 2024 MontaVista Software, LLC <source@mvista.com>

             Licensed under the Apache License, Version 2.0 (the "License");
             you may not use this file except in compliance with the License.
             You may obtain a copy of the License at

                http://www.apache.org/licenses/LICENSE-2.0

             Unless required by applicable law or agreed to in writing, software
             distributed under the License is distributed on an "AS IS" BASIS,
             WITHOUT WARRANTIES OR CONDITIONS OF ANY KIND, either express or
             implied.
             See the License for the specific language governing permissions and
             limitations under the License.";
    }
    container hello {
	leaf to {
	    type enumeration {
	        enum city;
		enum state;
		enum country;
		enum world;
	    }
	    description "To whom are we saying hello?";
	}
    }
}
